FME workspace FoodBankBufferer.fmw

Parameters:
- SourceDataset_GEODATABASE_FILE = C:\Users\mjggi\OneDrive\Desktop\Indexes\Indices.gdb   # File Geodatabase
- SourceDataset_GEODATABASE_FILE_3 = C:\Users\mjggi\OneDrive\Desktop\Indexes\Indices.gdb   # File Geodatabase
- FoodBankBuffer = 1600   # Food Bank Buffer Distance
- NFPIThreshold = 1.4   # NFPI Threshold
- DestDataset_GEODATABASE_FILE = C:\Users\mjggi\OneDrive\Desktop\Indexes\Indices.gdb   # File Geodatabase

Readers:
- GEODATABASE_FILE_1: GEODATABASE_FILE from $(SourceDataset_GEODATABASE_FILE)
- GEODATABASE_FILE_2: GEODATABASE_FILE from $(SourceDataset_GEODATABASE_FILE_3)

Writers:
- GEODATABASE_FILE_3: GEODATABASE_FILE to $(DestDataset_GEODATABASE_FILE)

Note: Create buffer around foodbank locations
Bufferer
    ANGLE = 22.5
    CAP_STYLE = Arc
    CORNER_STYLE = Arc
    MODE = AREA
    OFFSET = $(FoodBankBuffer)
    OFFSET_UNITS = NONE
    PRECISION = APPROX
    BUFFERED -> Dissolver
Note: Combine Buffers
Dissolver
    ACCUM_INPUT_ATTRS = Use Attributes From One Feature
    CLEANING_TOLERANCE = Automatic
    CONNECT_Z_MODE = First Wins
    DEAGGREGATE_INPUT = Yes
    AREA -> Clipper [CLIPPER]
    AREA -> Dissolver_Area
    AREA -> FoodBankCatchmentArea (writer GEODATABASE_FILE_3)
Note: Write FC to GDB
FoodBankCatchmentArea (writer GEODATABASE_FILE_3) [off]
    attributes: OBJECTID integer
Dissolver_Area: Inspector
FoodBanks: Inspector
Note: Reload FoodBanks
Junction_2
    -> NeighborFinder [CANDIDATE]
Note: FeatureMerger : Supplier
Junction_3
Note: Filter Leeds LSOAs
TestFilter
    DEFAULT_VALUE = <UNFILTERED>
    TEST_LIST = "BOOL_OP,OR,COMPOSITE_TEST,""""""1"""""",TEST_CLAUSE,CASE_INSENSITIVE_TEST @Value(LSOAName) CONTAINS Leeds",@Value(LSOAName) CONTAINS Leeds
    @Value(LSOAName) CONTAINS Leeds -> Tester
Note: Set NFPI threshold
Tester
    BOOL_OP = OR
    COMPOSITE_TEST = 1
    TEST_CLAUSE = TEST @Value(IndexValue) >= $(NFPIThreshold)
    TEST_MODE = TEST
    PASSED -> Clipper [CLIPPEE]
Note: Clip food bank buffers and vunerable areas
Clipper
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    OUTSIDE -> CenterPointExtractor
    OUTSIDE -> Junction_4
Note: FeatureMerger : Requestor
Junction_4
    -> Junction_5
Note: Clipper : Outside
Junction_5
    -> FeatureMerger [REQUESTOR]
Note: Calculate Distance to Nearest Food Bank
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> GeometryRemover_2
GeometryRemover_2
    -> FeatureMerger [SUPPLIER]
FeatureMerger
    ATTR_ACCUM_MODE = Merge Supplier
    ATTR_CONFLICT_RES = Use Requestor
    IGNORE_NULLS = No
    JOIN_KEYS = @Value(LSOAName) @Value(LSOAName) AUTO
    MERGE_TYPE = Attributes and Geometry
    PROCESS_DUPS = NO
    REJECT_NULL_MISSING_KEYS = No
    SUPPLIERS_FIRST = No
    MERGED -> AttributeManager
AttributeManager
    ATTR_TABLE:
      REMOVE OBJECTID
      REMOVE ZRenters
      REMOVE ZSocialClass
      REMOVE ZOnePersonHouse
      REMOVE ZSingleParents
      REMOVE ZDisablity
      REMOVE wRenters
      REMOVE wSocialClass
      REMOVE wOnePersonHouse
      REMOVE wSingleParents
      REMOVE wDisablity
      REMOVE IMDValue
      REMOVE SHAPE_Length
      REMOVE SHAPE_Area
      REMOVE DecileDiff
      RENAME_SET_VALUE _distance > DistanceToNearestFoodBank
      REMOVE _angle
      REMOVE _candidate_angle
      REMOVE _candidate_label_angle
      REMOVE _closest_candidate_x
      REMOVE _closest_candidate_y
      REMOVE _closest_base_x
      REMOVE _closest_base_y
    -> VulnerableAreas (writer GEODATABASE_FILE_3)
    -> AttributeManager_Output
Note: Write FC to GDB
VulnerableAreas (writer GEODATABASE_FILE_3)
    attributes: IndexValue double, GeographyCode char(9), LSOAName char(33), DistanceToNearestFoodBank smallint
AttributeManager_Output: Inspector

Bookmark: Load In Data
Note: Load in Food Bank Locations
FoodBanks (reader GEODATABASE_FILE_1)
    attributes: OBJECTID integer
    -> Bufferer
    -> Junction
    -> FoodBanks
Junction
    -> Junction_2
Note: Load in NFPI
IndexFinal (reader GEODATABASE_FILE_2)
    attributes: OBJECTID integer, ZRenters double, ZSocialClass double, ZOnePersonHouse double, ZSingleParents double, ZDisablity double, wRenters double, wSocialClass double, wOnePersonHouse double, wSingleParents double, wDisablity double, IndexValue double, GeographyCode char(9), LSOAName char(33), IMDValue integer, SHAPE_Length double, SHAPE_Area double, DecileDiff smallint
    -> TestFilter
    -> Junction_3

Bookmark: Create Centre Point of Area
Note: Define Centre Point of Area
CenterPointExtractor
    CENTX = _inside_x
    CENTY = _inside_y
    CENTZ = _inside_z
    EXTRACTIONMODE = CENTEROFGRAV
    -> GeometryRemover
GeometryRemover
    -> VertexCreator
VertexCreator
    MEASURE_TYPE = Continuous
    MISSING_VAL_MODE = Compute
    MODE_NAME = Add Point
    XVAL = @Value(_inside_x)
    YVAL = @Value(_inside_y)
    -> AttributeRemover
AttributeRemover
    REMOVE_ATTRS = _clipped,_fme_no_clipper,_inside_x,_inside_y,_inside_z,DecileDiff,GeographyCode,IMDValue,IndexValue,OBJECTID,SHAPE_Area,SHAPE_Length,wDisablity,wOnePersonHouse,wRenters,wSingleParents,wSocialClass,ZDisablity,ZOnePersonHouse,ZRenters,ZSingleParents,ZSocialClass
    -> NeighborFinder [BASE]
