FME workspace WriteNFPIToGBD.fmw

Parameters:
- SourceDataset_XLSXR = $(FME_MF_DIR)NFPIConstruction.xlsx   # Source Microsoft Excel File(s)
- SourceDataset_GEODATABASE_FILE = $(FME_MF_DIR)Indices.gdb   # File Geodatabase
- DestDataset_GEODATABASE_FILE = $(FME_MF_DIR)Indices.gdb   # File Geodatabase

Readers:
- XLSXR_1: XLSXR from $(SourceDataset_XLSXR)
- GEODATABASE_FILE_1: GEODATABASE_FILE from $(SourceDataset_GEODATABASE_FILE)

Writers:
- GEODATABASE_FILE_2: GEODATABASE_FILE to $(DestDataset_GEODATABASE_FILE)

Note: Load in NFPI Values
NFPIIndex (reader XLSXR_1)
    attributes: geography code char(10), ZRenters number(17,15), geography code00 char(10), ZSocialClass number(19,16), geography code01 char(10), ZOnePersonHouse number(20,17), geography code02 char(10), ZSingleParents number(20,17), geography code03 char(10), ZDisablity number(19,16), GeometriesCheck number(2,0), L string, wRenters number(18,16), wSocialClass number(19,16), wOnePersonHouse number(21,18), wSingleParents number(21,18), wDisablity number(20,17), IndexValue number(16,14), S string, Weights string, ZSocialRents number(4,2), Social Class number(4,2), ZOnePersonHouse00 number(4,2), ZSingleParents00 number(4,2), Z_Disablity number(4,2), Z number(2,0), AA string, AB string, AC string, AD string,
      AE string, Error With Geometry Codes? char(15)
    -> FeatureMerger [REQUESTOR]
Note: Load in LSOA Geometry
LSOA (reader GEODATABASE_FILE_1)
    attributes: OBJECTID integer, GeographyCode char(9), LSOAName char(33), SHAPE_Length double, SHAPE_Area double
    -> FeatureMerger [SUPPLIER]
FeatureMerger
    ATTR_ACCUM_MODE = Merge Supplier
    ATTR_CONFLICT_RES = Use Requestor
    IGNORE_NULLS = No
    JOIN_KEYS = @Value(geography code) @Value(GeographyCode) AUTO
    MERGE_TYPE = Attributes and Geometry
    PROCESS_DUPS = NO
    REJECT_NULL_MISSING_KEYS = No
    SUPPLIERS_FIRST = No
    MERGED -> NFPIIndex (writer GEODATABASE_FILE_2)
Note: Write out to relevent index
NFPIIndex (writer GEODATABASE_FILE_2)
    attributes: geography_code char(10), wRenters double(18,16), wSocialClass double(19,16), wOnePersonHouse double(21,18), wSingleParents double(21,18), wDisablity double(20,17), IndexValue double(16,14), GeographyCode char(9), LSOAName char(33)
